module cic-bgp {

  namespace "http://example.com/cic-bgp";
  prefix cic-bgp;

  import ietf-inet-types {
    prefix inet;
  }
  import tailf-common {
    prefix tailf;
  }
  import tailf-ncs {
    prefix ncs;
  }

  description
    "Bla bla...";

  revision 2016-01-01 {
    description
      "Initial revision.";
  }

  list cic-bgp {
    description "This is an RFS skeleton service";

    key name;
    leaf name {
      tailf:info "Unique service id";
      tailf:cli-allow-range;
      type string;
    }

    uses ncs:service-data;
    ncs:servicepoint cic-bgp-servicepoint;

    // may replace this with other ways of refering to the devices.
    leaf device1 {
      type leafref {
        path "/ncs:devices/ncs:device/ncs:name";
      }
    }
    leaf device2 {
      type leafref {
        path "/ncs:devices/ncs:device/ncs:name";
      }
    }
    leaf device3 {
      type leafref {
        path "/ncs:devices/ncs:device/ncs:name";
      }
    }

    // replace with your own stuff here
    leaf asn-dev1 {
      type inet:as-number;
    }
    leaf asn-dev2 {
      type inet:as-number;
    }
    leaf asn-dev3 {
      type inet:as-number;
    }
    leaf adv-route-dev1 {
      type inet:ipv4-address;
    }
    leaf adv-mask-dev1 {
      type inet:ipv4-address;
    }
    leaf adv-route-dev2 {
      type inet:ipv4-address;
    }
    leaf adv-mask-dev2 {
      type inet:ipv4-address;
    }
    leaf adv-route-dev3 {
      type inet:ipv4-address;
    }
    leaf adv-mask-dev3 {
      type inet:ipv4-address;
    }
  }
}
